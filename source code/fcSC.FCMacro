# ***************************************************************************
# *                                                                         *
# *   Copyright (c) 2024 - Harry van Langen <hvlanalysis@gmail.com>        *
# *                                                                         *
# *   This program is free software; you can redistribute it and/or modify  *
# *   it under the terms of the GNU Lesser General Public License (LGPL)    *
# *   as published by the Free Software Foundation; either version 2 of     *
# *   the License, or (at your option) any later version.                   *
# *   for detail see the LICENCE text file.                                 *
# *                                                                         *
# *   This program is distributed in the hope that it will be useful,       *
# *   but WITHOUT ANY WARRANTY; without even the implied warranty of        *
# *   MERCHANTABILITY or FITNESS FOR A PARTICULAR PURPOSE.  See the         *
# *   GNU Library General Public License for more details.                  *
# *                                                                         *
# *   You should have received a copy of the GNU Library General Public     *
# *   License along with this program; if not, write to the Free Software   *
# *   Foundation, Inc., 59 Temple Place, Suite 330, Boston, MA  02111-1307  *
# *   USA                                                                   *
# *                                                                         *
# ***************************************************************************

import os
import sys
import time
import math
import dummySC
import FreeCAD as App
import FreeCADGui as Gui

print("fcSC.FCMacro")

mdir = os.path.dirname(dummySC.file_path())
name = App.ActiveDocument.Label
file_path = os.path.join(mdir, "control files", name + '_sc.inp')
macro_path = os.path.join(mdir, 'source code')

global progress_update

fcSC_window.progressBar.setValue(0)
fcSC_window.Step.setText("0")
fcSC_window.Load_Factor.setText("0.000")
fcSC_window.eps_c.setText("0.000")
fcSC_window.eps_s.setText("0.000")

return_code = 0

def prn_upd(*args):
    for obj in args:
        print(str(obj), end='')
    print('\n')
    Gui.updateGui()


if 'fcSC' in sys.modules.keys():
    del (sys.modules['fcSC'])
    print("fcSC in sys.modules.keys")
else:
    sys.path.append(macro_path)
    print("fcSC path added")

import fcSC as ft

t = 7 * [0.0]

try:
    with open(file_path, encoding='utf8') as f:
        fcd = float(f.readline().strip())
        sig_yield = float(f.readline().strip())
        grav_z = float(f.readline().strip())
        rhox = float(f.readline().strip())
        rhoy = float(f.readline().strip())
        rhoz = float(f.readline().strip())
        nstep = int(f.readline().strip())
        iterat_max = int(f.readline().strip())
        error_max = float(f.readline().strip())
        relax = float(f.readline().strip())
        scale_re = float(f.readline().strip())
        scale_up = float(f.readline().strip())
        scale_dn = float(f.readline().strip())
        disp_output = f.readline().strip()
        target_LF_V = float(f.readline().strip())
        eps_option = f.readline().strip()
        averaged_option = f.readline().strip()
        model = int(f.readline().strip())
        target_LF_P = float(f.readline().strip())
        num_mat_obj = int(f.readline().strip())
        mat_obj = []
        for i in range(num_mat_obj):
            mat_obj.append([float(val) for val in str(f.readline().strip()).split()])
            for rho in mat_obj[-1][0:3]:
                if rho <= 0.0:
                    pass
                    # return_code = 5

except:
    print("file not found")

# print(mat_obj)
# extract information from FreeCAD objects
Gui.updateGui()
t0 = time.time()
doc, mesh, analysis, return_code = ft.setUpAnalysis(return_code)
t1 = time.time()
t[0] = t1 - t0
prn_upd(f"extract information from FreeCAD objects - time taken:  {t1 - t0:7.3f}  seconds\n")


if return_code == 1:
    prn_upd("No mesh object. Please create one first")
elif return_code == 2:
    prn_upd("No mesh. Please generate mesh first")
elif return_code == 3:
    prn_upd("No Analysis object. Please create one first")
elif return_code == 5:
    prn_upd("Encountered a zero or negative reinforcement ratio")

if return_code == 0:
    # prepare finite element input
    prn_upd("prepare finite element input\n")
    t0 = time.time()
    (elNodes, noCoord, fix, fixdof, movdof, elMat, noce, loadFaces, pressure, loadvertices, vertexloads,
     loadedges, edgeloads, loadfaces_uni, faceloads, ploadtype, vloadtype, eloadtype, floadtype, a_c, a_s,
     ev, return_code) = ft.setUpInput(doc, mesh, analysis, mat_obj, return_code)

    if return_code == 4:
        prn_upd("Not all elements belong to a material object")
    else:
        t1 = time.time()
        t[1] = t1 - t0
        prn_upd(f"prepare finite element input - time taken:  {t1 - t0:7.3f}  seconds\n")

        # calculate the global stiffness matrix and global load vector
        prn_upd("calculate the GSM and GLV\n")
        t0 = time.time()
        stm, row, col, glv_V, glv_P, modf, V, loadsumx_p, loadsumy_p, loadsumz_p, loadsumx_v, loadsumy_v, loadsumz_v, ne, nn, x = ft.calcGSM(
            elNodes, noCoord, elMat, fix, grav_z, rhox, rhoy, rhoz, loadFaces, pressure, loadvertices,
            vertexloads, loadedges,
            edgeloads, loadfaces_uni, faceloads, ploadtype, vloadtype, eloadtype, floadtype, a_c, a_s, ev, model, nstep)

        t1 = time.time()
        t[2] = t1 - t0
        prn_upd(f"calculate the GSM and GLV - time taken:  {t1 - t0:7.3f}  seconds\n")

        # solve the global stiffness matrix equation
        prn_upd("solve the global stiffness matrix equation\n")
        Gui.updateGui()
        t0 = time.time()

        displacements, stresses, epscc_new, cw_new, sigmises, epss_new, lbdp, unp, lbdv, unv, crip, peeqplot, pplot, svmplot, pdfcdplot, epsccplot, maxloc_epscc, cwplot, epssplot, maxloc_epss, fail, pdfcd = ft.calcDisp(
            elNodes, noCoord, fixdof, movdof, modf, elMat,
            stm, row, col, glv_V, glv_P, nstep, iterat_max,
            error_max, relax, scale_re, scale_up, scale_dn, fcd, sig_yield, disp_output,
            fcSC_window, target_LF_V, target_LF_P, x, noce, rhox, rhoy, rhoz, a_c, a_s, ev, fix, model)

        t1 = time.time()
        t[3] = t1 - t0
        prn_upd(f"solve the global stiffness matrix equation - time taken:  {t1 - t0:7.3f}  seconds\n")

        if not fail:
            # map stresses to nodal points
            prn_upd("map stresses and strains to nodal points\n")
            t0 = time.time()
            averaged = fcSC_window.averagedChk.isChecked()
            tet10stress, tet10epss, tet10epscc, tet10cw, tet10svm, tet10pdfcd = ft.mapStresses(averaged, elNodes,
                                                                                               noCoord, stresses,
                                                                                               epscc_new, cw_new,
                                                                                               sigmises, epss_new,
                                                                                               noce,
                                                                                               sig_yield, pdfcd)
            t1 = time.time()
            t[4] = t1 - t0

            prn_upd(f"map stresses to nodal points - time taken:  {t1 - t0:7.3f}  seconds\n")

            # export results to VTK
            prn_upd("export results to VTK\n")
            t0 = time.time()
            VTKfile = os.path.join(mdir, "output files", name + '.vtk')
            tet10rho = ft.exportVTK(elNodes, noCoord, displacements, tet10stress, tet10epss, tet10epscc, tet10cw,
                                    tet10svm, tet10pdfcd, sig_yield, VTKfile)
            t1 = time.time()
            t[6] = t1 - t0
            prn_upd(f"export results to VTK - time taken:  {t1 - t0:7.3f}  seconds\n")

            # paste results in the FEM result object
            prn_upd("paste results in the FEM result object\n")
            t0 = time.time()
            resVol = ft.pasteResults(doc, elNodes, noCoord, displacements, tet10stress, tet10epss, tet10epscc, tet10rho)
            t1 = time.time()
            t[5] = t1 - t0
            prn_upd(f"paste results in the FEM result object - time taken:  {t1 - t0:7.3f}  seconds\n")

        timer = [f"extract information from FreeCAD objects....................... {t[0]:7.3f} seconds",
                 f"prepare finite element input................................... {t[1]:7.3f} seconds",
                 f"calculate the global stiffness matrix and global load vector... {t[2]:7.3f} seconds",
                 f"solve the global siffness matrix equation...................... {t[3]:7.3f} seconds",
                 f"map stresses to nodal points................................... {t[4]:7.3f} seconds",
                 f"paste results in the FEM result object......................... {t[5]:7.3f} seconds",
                 f"export results to VTK.......................................... {t[6]:7.3f} seconds"]

        prn_upd("------------------------------ SUMMARY ------------------------------")
        for entry in timer:
            prn_upd(entry)

        file_path = os.path.join(mdir, "output files", name + '.out')

        with open(file_path, "w") as f:
            f.write("model name:{0: >30}\n".format(name))
            f.write("No. of elements:{0: >25}\n".format(ne))
            f.write("No. of Degrees of freedom:{0: >15}\n".format(nn))
            f.write(
                "\n=========================================================================================================================\n\n")
            f.write("Sum of permanent loads\n")
            f.write("x-direction: {0: >15.2e}\n".format(loadsumx_p))
            f.write("y-direction: {0: >15.2e}\n".format(loadsumy_p))
            f.write("z-direction: {0: >15.2e}\n\n".format(loadsumz_p))
            f.write("Sum of variable loads\n")
            f.write("x-direction: {0: >15.2e}\n".format(loadsumx_v))
            f.write("y-direction: {0: >15.2e}\n".format(loadsumy_v))
            f.write("z-direction: {0: >15.2e}\n".format(loadsumz_v))
            f.write(
                "\n=========================================================================================================================\n\n")
            f.write(
                "{0: >10}{1: >10}{2: >10}{3: >10}{4: >10}{5: >10}{6: >8}{7: >10}{8: >10}{9: >8}\n".format(
                    "lbd_p", "disp_p", "lbd_v", "disp_v", "p/fcd", "eps_cc", "ip_cc", "cw", "eps_s", "ip_cc"))
            for i in range(len(lbdp)):
                f.write(
                    '{0: >10.2e}{1: >10.2e}{2: >10.2e}{3: >10.2e}{4: >10.2e}{5: >10.2e}{6: >8}{7: >10.2e}{8: >10.2e}{9: >8}\n'.format(
                        lbdp[i], unp[i], lbdv[i], unv[i], pdfcdplot[i], epsccplot[i], maxloc_epscc[i], cwplot[i],
                        epssplot[i], maxloc_epss[i]))

            f.write(
                "\n=========================================================================================================================\n\n")

        f.close()

        fcSC_window.progressBar.setValue(0)
        fcSC_window.Step.setText("0")
        fcSC_window.Load_Factor.setText("0.000")
